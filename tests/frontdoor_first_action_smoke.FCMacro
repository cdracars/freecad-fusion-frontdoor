"""Exercise Frontdoor's first-action progression in a disposable FreeCAD profile.

Run this macro from a Frontdoor-enabled FreeCAD profile with no active document.
It records a JSON report at FRONTDOOR_UI_SMOKE_REPORT when that variable is set,
then closes the test document and FreeCAD window.
"""

import json
import os
import traceback

import FreeCAD as App
import FreeCADGui as Gui
import Part
from PySide import QtCore, QtWidgets
import task_surface as _task_surface_module


_report_path = os.environ.get(
    "FRONTDOOR_UI_SMOKE_REPORT",
    os.path.join(App.getUserAppDataDir(), "frontdoor_first_action_smoke.json"),
)
_report = {"steps": {}, "failures": []}
_main = Gui.getMainWindow()
_finished = False
_initial_toolbar_visibility = {}


def _surface():
    return next(
        (
            dock
            for dock in _main.findChildren(QtWidgets.QDockWidget)
            if dock.objectName() == "FrontdoorDesignTaskSurface"
        ),
        None,
    )


def _toolbars():
    return [
        toolbar
        for toolbar in _main.findChildren(QtWidgets.QToolBar)
        if toolbar.parentWidget() is _main
    ]


def _snapshot(label):
    dock = _surface()
    if dock is None:
        raise RuntimeError("Frontdoor Design task surface was not found.")
    dock.refresh_state()
    QtWidgets.QApplication.processEvents()
    visible_actions = [
        {"text": button.text(), "command": button.property("commandId"), "primary": button is dock.primary_button}
        for button in dock.findChildren(QtWidgets.QToolButton)
        if button.isVisible() and button.property("commandId")
    ]
    gui_document = Gui.activeDocument()
    in_edit = gui_document.getInEdit() if gui_document else None
    edit_object = getattr(in_edit, "Object", None) or in_edit
    state = {
        "active_document": App.ActiveDocument.Name if App.ActiveDocument else None,
        "primary_command": dock.primary_command,
        "visible_actions": visible_actions,
        "hint": dock.status.text(),
        "navigation_status": dock.navigation_status.text(),
        "fusion_navigation_enabled": App.ParamGet(
            "User parameter:BaseApp/Preferences/Mod/FreecadFusion"
        ).GetBool("Enabled", False),
        "editing_object": getattr(edit_object, "Name", None),
        "start_page_show_on_startup": App.ParamGet(
            "User parameter:BaseApp/Preferences/Mod/Start"
        ).GetBool("ShowOnStartup", True),
        "modal_dialogs": [
            widget.windowTitle()
            for widget in QtWidgets.QApplication.topLevelWidgets()
            if widget.isVisible() and isinstance(widget, QtWidgets.QDialog)
        ],
    }
    start_page = _main.findChild(QtWidgets.QWidget, "StartView")
    state["native_start_page_open"] = start_page is not None
    state["native_start_page_visible"] = bool(start_page and start_page.isVisible())
    state["native_task_docks"] = [
        {"title": dock.windowTitle(), "object_name": dock.objectName(), "visible": dock.isVisible()}
        for dock in _main.findChildren(QtWidgets.QDockWidget)
        if dock is not _surface() and dock.windowTitle().strip().casefold() == "tasks"
    ]
    state["toolbars"] = [
        {
            "title": toolbar.windowTitle(),
            "object_name": toolbar.objectName(),
            "hidden": toolbar.isHidden(),
            "visible": toolbar.isVisible(),
            "actions": [
                {
                    "text": action.text(),
                    "object_name": action.objectName(),
                    "enabled": action.isEnabled(),
                    "tooltip": action.toolTip(),
                    "has_icon": not action.icon().isNull(),
                }
                for action in toolbar.actions()
                if action.text()
            ],
        }
        for toolbar in _toolbars()
    ]
    state["menu_bar_visible"] = _main.menuBar().isVisible()
    available_commands = set(Gui.listCommands())
    state["quick_access_command_registration"] = {
        command: command in available_commands
        for command in ("Std_Open", "Std_Save", "Std_Undo", "Std_Redo")
    }
    state["quick_access"] = []
    for command, action_label in _task_surface_module._quick_access_commands:
        action = dock.quick_access_actions.get(command)
        if action is None:
            continue
        native_action = _task_surface_module._native_command_action(_main, command)
        button = dock.quick_access.widgetForAction(action)
        state["quick_access"].append(
            {
                "command": command,
                "label": action_label,
                "enabled": action.isEnabled(),
                "has_icon": not action.icon().isNull(),
                "same_native_action": action is native_action,
                "accessible_name": button.accessibleName() if button else None,
            }
        )
    if App.ActiveDocument:
        state["document_undo_counts"] = {}
        for name in ("UndoCount", "RedoCount"):
            value = getattr(App.ActiveDocument, name, None)
            if callable(value):
                try:
                    value = value()
                except Exception:
                    value = None
            state["document_undo_counts"][name] = value
    screen = QtWidgets.QApplication.primaryScreen()
    state["window_size"] = [_main.width(), _main.height()]
    state["display_scale_factor"] = screen.devicePixelRatio() if screen else None
    capture_path = os.path.splitext(_report_path)[0] + "_" + label + ".png"
    state["window_capture"] = capture_path
    _main.grab().save(capture_path)
    _report["steps"][label] = state
    return dock, state


def _require(condition, message):
    if not condition:
        _report["failures"].append(message)


def _tasks_dock_visible(state):
    return any(dock["visible"] for dock in state["native_task_docks"])


def _history_count(document, attribute):
    value = getattr(document, attribute, 0)
    return value() if callable(value) else value


def _trigger_and_cancel_dialog(command, timeout_ms=4000):
    dock = _surface()
    action = dock.quick_access_actions.get(command)
    if action is None:
        raise RuntimeError("Quick Access action %s is missing." % command)
    result = {"seen": [], "timed_out": False}
    deadline = QtCore.QTime.currentTime().addMSecs(timeout_ms)

    def reject_dialog():
        dialogs = [
            widget
            for widget in QtWidgets.QApplication.topLevelWidgets()
            if widget.isVisible() and isinstance(widget, QtWidgets.QDialog)
        ]
        if dialogs:
            result["seen"] = [
                {"title": dialog.windowTitle(), "class": dialog.metaObject().className()}
                for dialog in dialogs
            ]
            for dialog in dialogs:
                dialog.reject()
            return
        if QtCore.QTime.currentTime() >= deadline:
            result["timed_out"] = True
            return
        QtCore.QTimer.singleShot(100, reject_dialog)

    QtCore.QTimer.singleShot(100, reject_dialog)
    action.trigger()
    QtWidgets.QApplication.processEvents()
    return result


def _write_report():
    with open(_report_path, "w", encoding="utf-8") as stream:
        json.dump(_report, stream, indent=2)


def _finish():
    global _finished
    if _finished:
        return
    _finished = True
    try:
        gui_document = Gui.activeDocument()
        if gui_document and gui_document.getInEdit():
            gui_document.resetEdit()
        if App.ActiveDocument:
            App.closeDocument(App.ActiveDocument.Name)
        _report["cleanup_document_closed"] = App.ActiveDocument is None
    except Exception:
        _report["cleanup_error"] = traceback.format_exc()
    try:
        _write_report()
    finally:
        QtCore.QTimer.singleShot(500, _main.close)


def _check_no_document():
    global _initial_toolbar_visibility
    try:
        dock, state = _snapshot("no_document")
        _require(state["active_document"] is None, "Fresh profile unexpectedly opened a document.")
        _require(
            not state["start_page_show_on_startup"],
            "Fusion profile did not apply the expected default Start-page preference.",
        )
        _require(
            not state["native_start_page_open"],
            "FreeCAD's native Start page remained open in the Fusion profile.",
        )
        _require(state["primary_command"] == "Std_New", "New Design was not the sole primary action.")
        _require(len(state["visible_actions"]) == 1, "No-document state showed more than one modeling action.")
        _require("Next, create a sketch." in state["hint"], "No-document hint did not explain the next step.")
        _require(not _tasks_dock_visible(state), "The empty native Tasks dock remained visible at launch.")
        _require(state["menu_bar_visible"], "Frontdoor hid the native menu bar.")
        expected_navigation = (
            "Fusion navigation" if state["fusion_navigation_enabled"] else "FreeCAD navigation"
        )
        _require(
            state["navigation_status"] == expected_navigation,
            "Navigation status did not match the active add-on preset state.",
        )
        _require(
            all(toolbar["hidden"] for toolbar in state["toolbars"]),
            "Native toolbars were visible in Frontdoor's idle state.",
        )
        quick_commands = {item["command"] for item in state["quick_access"]}
        _require(
            quick_commands == {"Std_Open", "Std_Save", "Std_Undo", "Std_Redo"},
            "Quick Access did not provide exactly Open, Save, Undo, and Redo.",
        )
        _require(
            all(item["same_native_action"] for item in state["quick_access"]),
            "A Quick Access control did not reuse its native FreeCAD action.",
        )
        _require(
            all(item["has_icon"] and item["accessible_name"] == item["label"]
                for item in state["quick_access"]),
            "Quick Access is missing a native icon or accessible name.",
        )
        _require(
            next((item["enabled"] for item in state["quick_access"] if item["command"] == "Std_Open"), False),
            "Open was unavailable without an active document.",
        )
        _require(
            all(
                item["enabled"] == _task_surface_module._native_command_action(
                    _main, item["command"]
                ).isEnabled()
                for item in state["quick_access"]
            ),
            "Quick Access enabled state diverged from FreeCAD with no active document.",
        )
        _require(
            not any(item["command"] == "Std_New" for item in state["quick_access"]),
            "Quick Access duplicated the New Design task action.",
        )
        open_result = _trigger_and_cancel_dialog("Std_Open")
        _report["open_dialog_cancel"] = open_result
        _require(bool(open_result["seen"]), "Open did not show a cancelable native dialog.")
        _require(not open_result["timed_out"], "Open dialog did not appear before timeout.")
        _require(App.ActiveDocument is None, "Canceling Open changed the no-document state.")
        original_visibility = dict(_task_surface_module._toolbar_visibility)
        if original_visibility:
            simulated_hidden = next(iter(original_visibility))
            original_visibility[simulated_hidden] = False
            _task_surface_module._toolbar_visibility[simulated_hidden] = False
            _report["simulated_preexisting_hidden_toolbar"] = [
                simulated_hidden.windowTitle(),
                simulated_hidden.objectName(),
            ]
        _initial_toolbar_visibility = {
            (toolbar.windowTitle(), toolbar.objectName()): visible
            for toolbar, visible in original_visibility.items()
        }
        Gui.runCommand("Frontdoor_NativeToolbars")
        QtWidgets.QApplication.processEvents()
        _require(
            all(toolbar.isHidden() == (not was_visible)
                for toolbar, was_visible in original_visibility.items()),
            "Native Toolbars did not restore the captured toolbar visibility.",
        )
        Gui.runCommand("Frontdoor_NativeToolbars")
        QtWidgets.QApplication.processEvents()
        _require(
            all(toolbar.isHidden() for toolbar in _toolbars()),
            "Native Toolbars did not return to the focused idle layout.",
        )
        Gui.activateWorkbench("PartWorkbench")
        QtCore.QTimer.singleShot(700, _check_native_workbench_restore)
    except Exception:
        _report["probe_error"] = traceback.format_exc()
        _finish()


def _check_native_workbench_restore():
    try:
        toolbar_states = {
            (toolbar.windowTitle(), toolbar.objectName()): not toolbar.isHidden()
            for toolbar in _toolbars()
        }
        for key, expected_visible in _initial_toolbar_visibility.items():
            if key in toolbar_states:
                _require(
                    toolbar_states[key] == expected_visible,
                    "Leaving Frontdoor did not restore toolbar visibility for %r." % (key,),
                )
        Gui.activateWorkbench("FrontdoorWorkbench")
        QtCore.QTimer.singleShot(700, _check_frontdoor_toolbar_restore)
    except Exception:
        _report["probe_error"] = traceback.format_exc()
        _finish()


def _check_frontdoor_toolbar_restore():
    try:
        dock, state = _snapshot("frontdoor_return")
        _require(
            all(toolbar["hidden"] for toolbar in state["toolbars"]),
            "Frontdoor did not reapply its focused toolbar layout on return.",
        )
        if dock.primary_button:
            dock.primary_button.click()
        else:
            raise RuntimeError("New Design primary action is missing.")
        QtCore.QTimer.singleShot(1800, _check_empty_document)
    except Exception:
        _report["probe_error"] = traceback.format_exc()
        _finish()


def _check_empty_document():
    try:
        dock, state = _snapshot("empty_document")
        _require(state["active_document"] is not None, "New Design did not create a document.")
        _require(state["primary_command"] == "PartDesign_NewSketch", "Create Sketch did not become primary.")
        _require(
            all(action["command"] not in {"PartDesign_Pad", "PartDesign_Pocket", "PartDesign_Fillet", "PartDesign_Chamfer"}
                for action in state["visible_actions"]),
            "Downstream modeling actions were visible before their prerequisites.",
        )
        _require(not _tasks_dock_visible(state), "The native Tasks dock remained visible with no active task.")
        _require(
            all(
                item["enabled"] == _task_surface_module._native_command_action(
                    _main, item["command"]
                ).isEnabled()
                for item in state["quick_access"]
            ),
            "Quick Access enabled state diverged from FreeCAD's native actions.",
        )
        _require(
            all(toolbar["hidden"] for toolbar in state["toolbars"]),
            "Native toolbars were visible in the empty-document state.",
        )
        save_result = _trigger_and_cancel_dialog("Std_Save")
        _report["save_dialog_cancel"] = save_result
        _require(bool(save_result["seen"]), "Save did not show a cancelable native dialog.")
        _require(not save_result["timed_out"], "Save dialog did not appear before timeout.")
        _require(App.ActiveDocument is not None, "Canceling Save closed the active document.")
        _main.showNormal()
        _main.resize(1280, 720)
        QtWidgets.QApplication.processEvents()
        dock, compact = _snapshot("compact_empty_document")
        _require(
            any(action["primary"] and action["command"] == "PartDesign_NewSketch" for action in compact["visible_actions"]),
            "Create Sketch was not visible as the primary action at compact window size.",
        )
        _require(dock.status.isVisible(), "The next-step hint was clipped at compact window size.")
        if dock.primary_button:
            dock.primary_button.click()
        else:
            raise RuntimeError("Create Sketch primary action is missing.")
        QtCore.QTimer.singleShot(1800, _check_sketch_edit)
    except Exception:
        _report["probe_error"] = traceback.format_exc()
        _finish()


def _add_test_profile(sketch):
    corners = ((0, 0), (20, 0), (20, 20), (0, 20))
    for index, point in enumerate(corners):
        next_point = corners[(index + 1) % len(corners)]
        sketch.addGeometry(
            Part.LineSegment(
                App.Vector(point[0], point[1], 0),
                App.Vector(next_point[0], next_point[1], 0),
            ),
            False,
        )


def _check_sketch_edit():
    try:
        dock, state = _snapshot("sketch_edit")
        _require(state["editing_object"] is not None, "Create Sketch did not enter native sketch edit mode.")
        _require(dock.primary_command is None, "Solid command button remained active during sketch editing.")
        _require("closed profile" in state["hint"], "Sketch edit hint did not explain the next step.")
        _require(not state["modal_dialogs"], "A modal dialog appeared during default XY sketch creation.")
        _require(_tasks_dock_visible(state), "The native Tasks dock was hidden during sketch editing.")
        _require(
            all(
                item["enabled"] == _task_surface_module._native_command_action(
                    _main, item["command"]
                ).isEnabled()
                for item in state["quick_access"]
            ),
            "Quick Access enabled state diverged from FreeCAD during sketch editing.",
        )
        sketcher_group_names = {
            "Sketcher",
            "Edit Mode",
            "Geometries",
            "Constraints",
            "Sketcher Tools",
            "B-Spline Tools",
            "Visual Helpers",
        }
        visible_sketcher_groups = {
            toolbar["title"]
            for toolbar in state["toolbars"]
            if toolbar["title"] in sketcher_group_names and toolbar["visible"]
        }
        _require(
            visible_sketcher_groups == {"Edit Mode", "Geometries", "Constraints"},
            "Sketch edit did not show exactly the three focused Sketcher toolbars.",
        )
        actions_by_group = {
            toolbar["title"]: {action["text"] for action in toolbar["actions"]}
            for toolbar in state["toolbars"]
        }
        _require(
            {"Line", "Rectangle"}.issubset(actions_by_group.get("Geometries", set())),
            "The focused geometry toolbar is missing Line or Rectangle.",
        )
        _require(
            {"Dimension", "Horizontal/Vertical Constraint"}.issubset(
                actions_by_group.get("Constraints", set())
            ),
            "The focused constraint toolbar is missing common constraints.",
        )
        _require(
            "Leave Sketch" in actions_by_group.get("Edit Mode", set()),
            "The focused edit toolbar is missing Leave Sketch.",
        )
        _require(
            not _task_surface_module._NativeToolbarsCommand().IsActive(),
            "Toggle Native Toolbars remained active during a native sketch task.",
        )
        if _report.get("quick_access_history_tested"):
            sketch = App.ActiveDocument.getObject(state["editing_object"])
            _add_test_profile(sketch)
            Gui.activeDocument().resetEdit()
            QtCore.QTimer.singleShot(1200, _check_closed_profile)
            return
        sketch = App.ActiveDocument.getObject(state["editing_object"])
        sketch_name = sketch.Name
        object_names_before_undo = {obj.Name for obj in App.ActiveDocument.Objects}
        undo_count_before = _history_count(App.ActiveDocument, "UndoCount")
        undo_button = dock.quick_access.widgetForAction(
            dock.quick_access_actions["Std_Undo"]
        )
        _require(undo_button is not None and undo_button.isEnabled(), "Quick Access Undo was not enabled for the native sketch transaction.")
        Gui.Selection.clearSelection()
        sketch = None
        _report["quick_access_undo_before"] = {
            "objects": sorted(object_names_before_undo),
            "undo_count": undo_count_before,
        }
        _require(undo_count_before > 0, "The sketch edit did not create a native undo history entry.")
        undo_button.click()
        QtCore.QTimer.singleShot(400, lambda: _check_after_quick_access_undo(sketch_name, object_names_before_undo))
    except Exception:
        _report["probe_error"] = traceback.format_exc()
        _finish()


def _check_closed_profile():
    try:
        dock, state = _snapshot("closed_profile")
        sketch = next(
            (obj for obj in App.ActiveDocument.Objects if obj.TypeId == "Sketcher::SketchObject"),
            None,
        )
        _report["closed_profile_has_wire"] = bool(sketch and dock._has_closed_profile(sketch))
        _require(not _tasks_dock_visible(state), "The native Tasks dock remained visible after sketch editing ended.")
        _require(
            all(toolbar["hidden"] for toolbar in state["toolbars"]),
            "Native toolbars remained visible after sketch editing ended.",
        )
        _require(_report["closed_profile_has_wire"], "The generated test sketch did not produce a closed profile.")
        _require(state["primary_command"] == "PartDesign_Pad", "Pad did not become primary after closing a valid profile.")
        sketch = next(
            (obj for obj in App.ActiveDocument.Objects if obj.TypeId == "Sketcher::SketchObject"),
            None,
        )
        if sketch is None:
            raise RuntimeError("The test sketch disappeared before Pad task validation.")
        Gui.Selection.clearSelection()
        Gui.Selection.addSelection(sketch)
        if not dock.buttons.get("PartDesign_Pad"):
            raise RuntimeError("Pad action button is missing after sketch completion.")
        dock.buttons["PartDesign_Pad"].click()
        QtCore.QTimer.singleShot(1600, _check_feature_task)
    except Exception:
        _report["probe_error"] = traceback.format_exc()
        _finish()


def _check_after_quick_access_undo(sketch_name, object_names_before_undo):
    try:
        dock, state = _snapshot("quick_access_undo")
        object_names_after_undo = {obj.Name for obj in App.ActiveDocument.Objects}
        redo_count_after_undo = _history_count(App.ActiveDocument, "RedoCount")
        redo_button = dock.quick_access.widgetForAction(
            dock.quick_access_actions["Std_Redo"]
        )
        _report["quick_access_undo"] = {
            "objects_before": sorted(object_names_before_undo),
            "objects_after": sorted(object_names_after_undo),
            "undo_count_after": _history_count(App.ActiveDocument, "UndoCount"),
            "redo_count_after": redo_count_after_undo,
            "redo_enabled_after": redo_button.isEnabled() if redo_button else False,
        }
        _require(
            sketch_name in object_names_before_undo and sketch_name not in object_names_after_undo,
            "Quick Access Undo did not undo the native sketch creation transaction.",
        )
        _require(
            redo_count_after_undo > 0 and redo_button is not None and redo_button.isEnabled(),
            "Quick Access Undo did not enable native Redo.",
        )
        if redo_button is None or not redo_button.isEnabled():
            _finish()
            return
        redo_button.click()
        QtCore.QTimer.singleShot(400, lambda: _check_after_quick_access_redo(sketch_name, object_names_before_undo))
    except Exception:
        _report["probe_error"] = traceback.format_exc()
        _finish()


def _check_after_quick_access_redo(sketch_name, object_names_before_undo):
    try:
        dock, state = _snapshot("quick_access_redo")
        object_names_after_redo = {obj.Name for obj in App.ActiveDocument.Objects}
        sketch = App.ActiveDocument.getObject(sketch_name)
        _report["quick_access_redo"] = {
            "objects_before": sorted(object_names_before_undo - {sketch_name}),
            "objects_after": sorted(object_names_after_redo),
            "undo_count_after": _history_count(App.ActiveDocument, "UndoCount"),
            "redo_count_after": _history_count(App.ActiveDocument, "RedoCount"),
        }
        _require(
            object_names_after_redo == object_names_before_undo and sketch is not None,
            "Quick Access Redo did not restore the sketch state.",
        )
        if sketch is None:
            raise RuntimeError("Redo did not restore the sketch needed for Pad validation.")
        _require(not sketch.Geometry, "Redo did not restore the sketch's pre-geometry state.")
        _report["quick_access_history_tested"] = True
        _report["quick_access_history_verified"] = not _report["failures"]
        document_name = App.ActiveDocument.Name
        App.closeDocument(document_name)
        dock.refresh_state()
        QtWidgets.QApplication.processEvents()
        _require(dock.primary_command == "Std_New", "Frontdoor did not return to New Design after closing the history probe document.")
        if dock.primary_button:
            dock.primary_button.click()
            QtCore.QTimer.singleShot(1500, _check_empty_document)
        else:
            raise RuntimeError("New Design was not available after closing the history probe document.")
    except Exception:
        _report["probe_error"] = traceback.format_exc()
        _finish()


def _check_feature_task():
    try:
        _, state = _snapshot("feature_task")
        _require(state["editing_object"] is not None, "Pad did not enter its native edit task.")
        _require(_tasks_dock_visible(state), "The native Tasks dock was hidden during Pad editing.")
        _require(
            not any(
                toolbar["visible"]
                and toolbar["title"] in {
                    "Sketcher",
                    "Edit Mode",
                    "Geometries",
                    "Constraints",
                    "Sketcher Tools",
                    "B-Spline Tools",
                    "Visual Helpers",
                }
                for toolbar in state["toolbars"]
            ),
            "Sketcher-only toolbars appeared during a non-sketch feature task.",
        )
        Gui.activeDocument().resetEdit()
        QtCore.QTimer.singleShot(900, _check_after_feature_cancel)
    except Exception:
        _report["probe_error"] = traceback.format_exc()
        _finish()


def _check_after_feature_cancel():
    try:
        _, state = _snapshot("feature_task_canceled")
        _require(state["editing_object"] is None, "Cancel did not close the Pad edit task.")
        _require(not _tasks_dock_visible(state), "The native Tasks dock remained visible after Pad cancel.")
        _require(
            all(toolbar["hidden"] for toolbar in state["toolbars"]),
            "Native toolbar rows remained visible after Pad cancel.",
        )
        _finish()
    except Exception:
        _report["probe_error"] = traceback.format_exc()
        _finish()


QtCore.QTimer.singleShot(5000, _check_no_document)
